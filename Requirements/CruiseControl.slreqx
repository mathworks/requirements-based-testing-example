# CruiseControl

## #1: Interface (Container)
All interface requirements

### #2: Enable/Disable Switch (Functional)
The controller shall have an On/Off Switch to enable/disable the operation of the cruise control system.

### #3: Set Speed/Decelerate Button (Functional)
The controller shall have an input button to:
- set the target speed to the current vehicle speed when the cruise control is not engaged (active)
- decelerate (reduce) the target speed when the cruise control is engaged (active)

### #4: Resume Speed/Accelerate Button (Functional)
The controller shall have an input button to:
- set the target speed to last acceptable target speed when the cruise control is not engaged (active)
- accelerate (increase) the target speed when the cruise control is active

### #5: Vehicle Speed Input (Functional)
The controller shall have a vehicle speed input to be used by the target speed algorithm.

### #6: Vehicle Brake Input (Functional)
The controller shall have a vehicle brake input to indicate when the driver has applied the brake pedal.

### #8: Engaged (active) Output (Functional)
The controller shall have an output signal to indicate that the controller is engaged (active) .

### #9: Target Speed Output (Functional)
The controller shall have an output signal to indicate that the target speed of the controller.

## #10: Functional (Container)
All non-safety functional requirements

### #14: Disabled (off) during start-up (Functional)
Initial state of cruise control system shall be disabled.

### #15: Not engaged with enabling (on) (Functional)
The cruise control system shall not be initially engaged with enabling.

### #16: Disengaged (not active) when disabled (off) (Functional)
The cruise control system shall disengage with disabling.

### #17: Initial transition from disengaged (inactive) to engaged (active) only with “Set Speed” input after enabling (on) (Functional)
The cruise control shall only transition to engaged (active) the first time after the system has been enabled with a “Set Speed” input. Target speed will be set to current vehicle speed.

### #18: “Resume” input ignored until the initial transition from disengaged (inactive) to engaged (active) (Functional)
The cruise control shall ignore the “Resume” input until the initial transition to engaged (active) the first time after the system has been enabled.

### #19: Subsequent transition from disengaged (inactive) to engaged (active) with “Set Speed” input while enabled (on) (Functional)
The cruise control shall transition to engaged (active) from disengaged with a “Set Speed” input when the system is enabled.

### #20: Subsequent transition from disengaged (inactive) to engaged (active) with “Resume” input while enabled (on) (Functional)
The cruise control shall transition to engaged (active) from disengaged after the initial transition to engaged (active).

### #21: “Accelerate” input increases target speed only when engaged (active) (Functional)
The target speed of the cruise control system shall increase by (1 mph, up to the limit) for the “Accelerate” input only when engaged. The “Accelerate” input is ignored when disengaged.

### #22: “Decelerate” input decreases target speed only when engaged (active) (Functional)
The target speed of the cruise control system shall decrease by (1 mph, down to the limit) for the “Decelerate” input only when engaged. The “Decelerate” input is ignored when disengaged.

### #23: Continuous “Accelerate” input increases target speed at a fixed rate and only when engaged (active) (Functional)
The target speed of the cruise control system shall increase by a fixed rate (tunable) when the “Accelerate” input is continuously held and only when engaged. A continuously held “Accelerate” input is ignored when disengaged.

### #24: Continuous “Decelerate” input decreases target speed at a fixed rate and only when engaged (active) (Functional)
The target speed of the cruise control system shall decrease by a fixed rate (tunable) when the “Decelerate” input is continuously held and only when engaged. A continuously held “Decelerate” input is ignored when disengaged.

## #25: Safety (Container)
All safety derived functional requirements

### #26: Vehicle braking will transition system to disengaged (inactive) when engaged (active) (Functional)
The cruise control system shall transition to disengaged from engaged when a braking event has occurred.

### #27: Transition to engaged (active) will only be permitted for vehicle speeds between 20 and 90 mph (Functional)
The cruise control system target speed shall not transition to engaged unless the current vehicle speed is between 20 and 90 mph for safe operation.

### #28: Transition to disengaged (inactive) when vehicle speed is outside the limits of 20 to 90 mph (Functional)
The cruise control system target speed shall transition to disengaged when the current vehicle speed is outside the limits of 20 to 90 mph for safe operation.

### #29: Target speed will be limited between 20 and 90 mph (Functional)
The cruise control system target speed shall be limited between 20 and 90 mph for safe operation.

### #34: Disengage when braking occurs (Functional)
The cruise control system shall transition to disengaged from engaged within 0.25 seconds after a braking event has occurred.

## #30: Justifications

### #31: Functional heading

### #32: Interface heading
